package EnglishPump {
    doc /* Synthetic controlled-English study; no engineering acceptance is claimed. */
    part def Pump;
    part pump : Pump {
        doc description /* The pump moves water. */
    }
    action def Isolate {
        doc description /* Isolate the pump. */
    }
}
